FME workspace CSWT_keyword_BGDI.fmw

Parameters:
- AUTH_PASSWORD =
- AUTH_USERNAME =
- SourceDataset_CSV2_3 =

Readers:
- CSV2_1: CSV2 from $(SourceDataset_CSV2_3)

DuplicateRemover_2
    KEYATTR = uuid
    UNIQUE -> StringConcatenator_2
StringConcatenator_2
    PARM_LINE:
      <?xml version="1.0" encoding="UTF-8"?>
      <csw:Transaction service="CSW" version="2.0.2" xmlns:csw="http://www.opengis.net/cat/csw/2.0.2" xmlns:ogc="http://www.opengis.net/ogc" xmlns:apiso="http://www.opengis.net/cat/csw/apiso/1.0" xmlns:srv="http://www.isotc211.org/2005/srv" xmlns:gco="http://www.isotc211.org/2005/gco" xmlns:che="http://www.geocat.ch/2008/che" xmlns:xsi="http://www.w3.org/2001/XMLSchema-instance" xmlns:gml="http://www.opengis.net/gml" xmlns:gmd="http://www.isotc211.org/2005/gmd">
      	<csw:Update>
      		<csw:RecordProperty>
      			<csw:Name>che:CHE_MD_Metadata/gmd:identificationInfo/che:CHE_MD_DataIdentification</csw:Name>
      			<csw:Value>
      				<gn_add>
      					<gmd:descriptiveKeywords xmlns:xlink="http://www.w3.org/1999/xlink">
      						<gmd:MD_Keywords>
      							<gmd:keyword xmlns:xsi="http://www.w3.org/2001/XMLSchema-instance" xsi:type="gmd:PT_FreeText_PropertyType">
      								<gmd:PT_FreeText>
      									<gmd:textGroup>
      										<gmd:LocalisedCharacterString locale="#EN">FSDI Federal Spatial Data Infrastructure</gmd:LocalisedCharacterString>
      									</gmd:textGroup>
      									<gmd:textGroup>
      										<gmd:LocalisedCharacterString locale="#DE">BGDI Bundesgeodaten-Infrastruktur</gmd:LocalisedCharacterString>
      									</gmd:textGroup>
      									<gmd:textGroup>
      										<gmd:LocalisedCharacterString locale="#IT">IFDG Infrastruttura federale dei dati geografici</gmd:LocalisedCharacterString>
      									</gmd:textGroup>
      									<gmd:textGroup>
      										<gmd:LocalisedCharacterString locale="#FR">IFDG l’Infrastructure Fédérale de données géographiques</gmd:LocalisedCharacterString>
      									</gmd:textGroup>
      								</gmd:PT_FreeText>
      							</gmd:keyword>
      							<gmd:type>
      								<gmd:MD_KeywordTypeCode codeList="http://www.isotc211.org/2005/resources/codeList.xml#MD_KeywordTypeCode" codeListValue="theme"/>
      							</gmd:type>
      							<gmd:thesaurusName>
      								<gmd:CI_Citation>
      									<gmd:title>
      										<gco:CharacterString>geocat.ch</gco:CharacterString>
      									</gmd:title>
      									<gmd:date>
      										<gmd:CI_Date>
      											<gmd:date>
      												<gco:Date>2021-06-18</gco:Date>
      											</gmd:date>
      											<gmd:dateType>
      												<gmd:CI_DateTypeCode codeList="http://standards.iso.org/iso/19139/resources/gmxCodelists.xml#CI_DateTypeCode" codeListValue="publication"/>
      											</gmd:dateType>
      										</gmd:CI_Date>
      									</gmd:date>
      									<gmd:identifier>
      										<gmd:MD_Identifier>
      											<gmd:code>
      												<gmx:Anchor xmlns:gmx="http://www.isotc211.org/2005/gmx" xlink:href="https://geocat-int.dev.bgdi.ch/geonetwork/srv/eng/thesaurus.download?ref=local.theme.geocat.ch">geonetwork.thesaurus.local.theme.geocat.ch</gmx:Anchor>
      											</gmd:code>
      										</gmd:MD_Identifier>
      									</gmd:identifier>
      								</gmd:CI_Citation>
      							</gmd:thesaurusName>
      						</gmd:MD_Keywords>
      					</gmd:descriptiveKeywords>
      				</gn_add>
      			</csw:Value>
      		</csw:RecordProperty>
      		<csw:Constraint version="1.1.0">
      			<ogc:Filter>
      				<ogc:PropertyIsEqualTo>
      					<ogc:PropertyName>Identifier</ogc:PropertyName>
      					<ogc:Literal>@Value(uuid)</ogc:Literal>
      				</ogc:PropertyIsEqualTo>
      			</ogc:Filter>
      		</csw:Constraint>
      	</csw:Update>
      </csw:Transaction>
    VAL_ATTR = post_body
    -> Decelerator

Bookmark: Test mit nur einer UUID
Starter [off]
    -> AttributeCreator [off]
AttributeCreator [off]
    ATTR_TABLE = SET_TO uuid = 4fd79ded-22f0-4296-883c-9c729e87d90c
    -> DuplicateRemover_2 [off]

Bookmark: Mit einer Liste von UUIDs
CSV (reader CSV2_1)
    attributes: uuid string, title string, org string
    -> DuplicateRemover_2

Bookmark: create post body and call csw-t interface
Decelerator
    DECEL_TYPE = Per Feature Delay
    DELAY = 5
    -> HTTPUploader
Note: CSW-T Interface Caller
HTTPUploader
    AUTH_METHOD = Basic
    AUTH_PASSWORD = $(AUTH_PASSWORD)
    AUTH_USERNAME = $(AUTH_USERNAME)
    ERROR_ATTR = _error
    FOLLOW_REDIRECTS = Yes
    PROXY_AUTH_METHOD = Basic
    PROXY_PORT = 8080
    PROXY_URL = http://proxy-bvcol.admin.ch
    RESPONSE_HEADER_LIST_ATTR = _headers
    STATUS_CODE_ATTR = _http_status_code
    TARGET_ATTR = _url_contents
    TARGET_ATTR_ENCODING = utf-8
    TARGET_URL = https://geocat-int.dev.bgdi.ch/geonetwork/srv/eng/csw-publication
    UPLOAD_BODY = @Value(post_body)
    UPLOAD_CONTENT_TYPE = application/xml
    UPLOAD_METHOD = POST
    USE_COOKIES = Yes
    VERIFY_SSL_CERTIFICATES = Yes
    -> http_status
    <REJECTED> -> HTTPUploader__Rejected_
http_status: TestFilter
    DEFAULT_VALUE = <UNFILTERED>
    TEST_LIST = BOOL_OP,OR,COMPOSITE_TEST,<Unused>,TEST_CLAUSE,"TEST @Value(_http_status_code) = 200",200
    200 -> TestFilter_200
    <UNFILTERED> -> TestFilter__Unfiltered_
TestFilter_200: Inspector
TestFilter__Unfiltered_: Inspector
HTTPUploader__Rejected_: Inspector

FME custom transformer Starter
This transformer is intended to start a workspace branch without the use of the creator transformer. This will end up without additional attributes (_creation_instance) at the end of the workspace.

Creator
    GEOMTYPE = Geometry Object
    NUM = 1
    CREATED -> Output (output)
Output (output)
