FME workspace CSWT_replace_keywords_single.fmw

Parameters:
- AUTH_PASSWORD =
- AUTH_USERNAME =
- SourceDataset_CSV2 =

Readers:
- CSV2_1: CSV2 from $(SourceDataset_CSV2)

Note: Delete Keyword funktioniert noch nicht (in txt-file sind verschiedene Optionen markiert zum ausprobieren...)
remove_duplicate_uuids: DuplicateRemover
    KEYATTR = uuid
    UNIQUE -> filter_on_languages
filter_on_languages: AttributeFilter
    ATTR_NAME = several_languages
    ATTR_VALUES = <Empty>,<Missing>,<Null>,<Unfiltered>,yes,no
    yes -> create_body_delete
    no -> create_body_delete_2
AttributeFilter
    ATTR_NAME = new_keyword_present
    ATTR_VALUES = <Empty>,<Missing>,<Null>,<Unfiltered>,yes,no
    no -> AttributeFilter_2
AttributeFilter_2
    ATTR_NAME = type
    ATTR_VALUES = <Empty>,<Missing>,<Null>,<Unfiltered>,geocat,gemet
    geocat -> StringConcatenator_2
    gemet -> StringConcatenator_4
AttributeFilter_4
    ATTR_NAME = new_keyword_present
    ATTR_VALUES = <Empty>,<Missing>,<Null>,<Unfiltered>,yes,no
    no -> AttributeFilter_5
AttributeFilter_5
    ATTR_NAME = type
    ATTR_VALUES = <Empty>,<Missing>,<Null>,<Unfiltered>,geocat,gemet
    geocat -> StringConcatenator_5
    gemet -> StringConcatenator_7

Bookmark: Test mit nur einer UUID
Starter [off]
    -> AttributeCreator [off]
AttributeCreator [off]
    ATTR_TABLE:
      SET_TO uuid = dc9568f7-9683-45c4-94ac-a7f0e652fc70
      SET_TO new_keyword_present = yes
      SET_TO type = geocat
      SET_TO several_languages = yes
    -> remove_duplicate_uuids [off]

Bookmark: Mit einer Liste von UUIDs
CSV (reader CSV2_1)
    attributes: uuid string, new_keyword_present string, several_languages string, type string
    -> remove_duplicate_uuids

Bookmark: Delete Keyword
create_body_delete: StringConcatenator
    PARM_LINE:
      <?xml version="1.0" encoding="UTF-8"?>
      <csw:Transaction service="CSW" version="2.0.2" xmlns:csw="http://www.opengis.net/cat/csw/2.0.2" xmlns:ogc="http://www.opengis.net/ogc" xmlns:apiso="http://www.opengis.net/cat/csw/apiso/1.0" xmlns:srv="http://www.isotc211.org/2005/srv" xmlns:gco="http://www.isotc211.org/2005/gco" xmlns:che="http://www.geocat.ch/2008/che" xmlns:xsi="http://www.w3.org/2001/XMLSchema-instance" xmlns:gml="http://www.opengis.net/gml" xmlns:gmd="http://www.isotc211.org/2005/gmd">
      	<csw:Update>
      		<csw:RecordProperty>
                  <csw:Name>che:CHE_MD_Metadata/gmd:identificationInfo/che:CHE_MD_DataIdentification/gmd:descriptiveKeywords/gmd:MD_Keywords/gmd:keyword/gmd:PT_FreeText/gmd:textGroup/gmd:LocalisedCharacterString[@locale='#DE' and contains(text(), 'Gemeindegrenze')]/../../..</csw:Name>
      			<csw:Value>
      				<gn_delete>
      				</gn_delete>
      			</csw:Value>
      		</csw:RecordProperty>
      		<csw:Constraint version="1.1.0">
      			<ogc:Filter>
      				<ogc:PropertyIsEqualTo>
      					<ogc:PropertyName>Identifier</ogc:PropertyName>
      					<ogc:Literal>@Value(uuid)</ogc:Literal>
      				</ogc:PropertyIsEqualTo>
      			</ogc:Filter>
      		</csw:Constraint>
      	</csw:Update>
      </csw:Transaction>
    VAL_ATTR = post_body_delete
    -> Decelerator_2
Decelerator_2
    DECEL_TYPE = Per Feature Delay
    DELAY = 2
    -> HTTPUploader_2
Note: CSW-T Interface Caller
HTTPUploader_2
    AUTH_METHOD = Basic
    AUTH_PASSWORD = $(AUTH_PASSWORD)
    AUTH_USERNAME = $(AUTH_USERNAME)
    ERROR_ATTR = _error
    FOLLOW_REDIRECTS = Yes
    PROXY_AUTH_METHOD = Basic
    PROXY_PORT = 8080
    PROXY_URL = http://proxy-bvcol.admin.ch
    RESPONSE_HEADER_LIST_ATTR = _headers
    STATUS_CODE_ATTR = _http_status_code
    TARGET_ATTR = _url_contents
    TARGET_ATTR_ENCODING = utf-8
    TARGET_URL = https://geocat-int.dev.bgdi.ch/geonetwork/srv/eng/csw-publication
    UPLOAD_BODY = @Value(post_body_delete)
    UPLOAD_CONTENT_TYPE = application/xml
    UPLOAD_METHOD = POST
    USE_COOKIES = Yes
    VERIFY_SSL_CERTIFICATES = Yes
    -> http_status_2
    <REJECTED> -> HTTPUploader__Rejected__2
http_status_2: TestFilter
    DEFAULT_VALUE = <UNFILTERED>
    TEST_LIST = BOOL_OP,OR,COMPOSITE_TEST,<Unused>,TEST_CLAUSE,"TEST @Value(_http_status_code) = 200",200
    200 -> TestFilter_2
    200 -> AttributeFilter
    <UNFILTERED> -> TestFilter__Unfiltered__2
TestFilter_2: Inspector
TestFilter__Unfiltered__2: Inspector
HTTPUploader__Rejected__2: Inspector

Bookmark: Add Keyword
Note: GEOCAT: BGDI wird hinzugefügt
StringConcatenator_2
    PARM_LINE:
      fme_basicstring:3205%12%115:<?xml version="1.0" encoding="UTF-8"?>
      <csw:Transaction service="CSW" version="2.0.2" xmlns:csw="http://www.opengis.net/cat/csw/2.0.2" xmlns:ogc="http://www.opengis.net/ogc" xmlns:apiso="http://www.opengis.net/cat/csw/apiso/1.0" xmlns:srv="http://www.isotc211.org/2005/srv" xmlns:gco="http://www.isotc211.org/2005/gco" xmlns:che="http://www.geocat.ch/2008/che" xmlns:xsi="http://www.w3.org/2001/XMLSchema-instance" xmlns:gml="http://www.opengis.net/gml" xmlns:gmd="http://www.isotc211.org/2005/gmd">
      	<csw:Update>
      		<csw:RecordProperty>
      			<csw:Name>che:CHE_MD_Metadata/gmd:identificationInfo/che:CHE_MD_DataIdentification</csw:Name>
      			<csw:Value>
      				<gn_add>
      					<gmd:descriptiveKeywords xmlns:xlink="http://www.w3.org/1999/xlink">
      						<gmd:MD_Keywords>
      							<gmd:keyword xmlns:xsi="http://www.w3.org/2001/XMLSchema-instance" xsi:type="gmd:PT_FreeText_PropertyType">
      								<gco:CharacterString>BGDI Bundesgeodaten-Infrastruktur</gco:CharacterString>
                                      <gmd:PT_FreeText>
      									<gmd:textGroup>
      										<gmd:LocalisedCharacterString locale="#EN">FSDI Federal Spatial Data Infrastructure</gmd:LocalisedCharacterString>
      									</gmd:textGroup>
      									<gmd:textGroup>
      										<gmd:LocalisedCharacterString locale="#DE">BGDI Bundesgeodaten-Infrastruktur</gmd:LocalisedCharacterString>
      									</gmd:textGroup>
      									<gmd:textGroup>
      										<gmd:LocalisedCharacterString locale="#IT">IFDG Infrastruttura federale dei dati geografici</gmd:LocalisedCharacterString>
      									</gmd:textGroup>
      									<gmd:textGroup>
      										<gmd:LocalisedCharacterString locale="#FR">IFDG l’Infrastructure Fédérale de données géographiques</gmd:LocalisedCharacterString>
      									</gmd:textGroup>
      								</gmd:PT_FreeText>
      							</gmd:keyword>
      							<gmd:type>
      								<gmd:MD_KeywordTypeCode codeList="http://www.isotc211.org/2005/resources/codeList.xml#MD_KeywordTypeCode" codeListValue="theme"/>
      							</gmd:type>
      							<gmd:thesaurusName>
      								<gmd:CI_Citation>
      									<gmd:title>
      										<gco:CharacterString>geocat.ch</gco:CharacterString>
      									</gmd:title>
      									<gmd:date>
      										<gmd:CI_Date>
      											<gmd:date>
      												<gco:Date>2021-06-18</gco:Date>
      											</gmd:date>
      											<gmd:dateType>
      												<gmd:CI_DateTypeCode codeList="http://standards.iso.org/iso/19139/resources/gmxCodelists.xml#CI_DateTypeCode" codeListValue="publication"/>
      											</gmd:dateType>
      										</gmd:CI_Date>
      									</gmd:date>
      									<gmd:identifier>
      										<gmd:MD_Identifier>
      											<gmd:code>
      												<gmx:Anchor xmlns:gmx="http://www.isotc211.org/2005/gmx" xlink:href="https://geocat-int.dev.bgdi.ch/geonetwork/srv/eng/thesaurus.download?ref=local.theme.geocat.ch">geonetwork.thesaurus.local.theme.geocat.ch</gmx:Anchor>
      											</gmd:code>
      										</gmd:MD_Identifier>
      									</gmd:identifier>
      								</gmd:CI_Citation>
      							</gmd:thesaurusName>
      						</gmd:MD_Keywords>
      					</gmd:descriptiveKeywords>
      				</gn_add>
      			</csw:Value>
      		</csw:RecordProperty>
      		<csw:Constraint version="1.1.0">
      			<ogc:Filter>
      				<ogc:PropertyIsEqualTo>
      					<ogc:PropertyName>Identifier</ogc:PropertyName>
      					<ogc:Literal>@Value(uuid)</ogc:Literal>
      				</ogc:PropertyIsEqualTo>
      			</ogc:Filter>
      		</csw:Constraint>
      	</csw:Update>
      </csw:Transaction>
    VAL_ATTR = post_body_add
    -> Decelerator
Note: GEMET: Bach wird hinzugefügt
StringConcatenator_4
    PARM_LINE:
      <?xml version="1.0" encoding="UTF-8"?>
      <csw:Transaction service="CSW" version="2.0.2" xmlns:csw="http://www.opengis.net/cat/csw/2.0.2" xmlns:ogc="http://www.opengis.net/ogc" xmlns:apiso="http://www.opengis.net/cat/csw/apiso/1.0" xmlns:srv="http://www.isotc211.org/2005/srv" xmlns:gco="http://www.isotc211.org/2005/gco" xmlns:che="http://www.geocat.ch/2008/che" xmlns:xsi="http://www.w3.org/2001/XMLSchema-instance" xmlns:gml="http://www.opengis.net/gml" xmlns:gmd="http://www.isotc211.org/2005/gmd">
      	<csw:Update>
      		<csw:RecordProperty>
      			<csw:Name>che:CHE_MD_Metadata/gmd:identificationInfo/che:CHE_MD_DataIdentification</csw:Name>
      			<csw:Value>
      				<gn_add>
      					<gmd:descriptiveKeywords xmlns:xlink="http://www.w3.org/1999/xlink">
      						<gmd:MD_Keywords>
      							<gmd:keyword xmlns:xsi="http://www.w3.org/2001/XMLSchema-instance" xsi:type="gmd:PT_FreeText_PropertyType">
      								<gco:CharacterString>Verwaltungsgrenze</gco:CharacterString>
      								<gmd:PT_FreeText>
      									<gmd:textGroup>
      										<gmd:LocalisedCharacterString locale="#DE">Verwaltungsgrenze</gmd:LocalisedCharacterString>
      									</gmd:textGroup>
      									<gmd:textGroup>
      										<gmd:LocalisedCharacterString locale="#FR">limite administrative</gmd:LocalisedCharacterString>
      									</gmd:textGroup>
      									<gmd:textGroup>
      										<gmd:LocalisedCharacterString locale="#IT">confine amministrativo</gmd:LocalisedCharacterString>
      									</gmd:textGroup>
      									<gmd:textGroup>
      										<gmd:LocalisedCharacterString locale="#EN">administrative boundary</gmd:LocalisedCharacterString>
      									</gmd:textGroup>
      								</gmd:PT_FreeText>
      							</gmd:keyword>
      							<gmd:type>
      								<gmd:MD_KeywordTypeCode codeList="http://www.isotc211.org/2005/resources/codeList.xml#MD_KeywordTypeCode" codeListValue="theme"/>
      							</gmd:type>
      							<gmd:thesaurusName>
      								<gmd:CI_Citation>
      									<gmd:title>
      										<gco:CharacterString>GEMET</gco:CharacterString>
      									</gmd:title>
      									<gmd:date>
      										<gmd:CI_Date>
      											<gmd:date>
      												<gco:Date>2018-08-16</gco:Date>
      											</gmd:date>
      											<gmd:dateType>
      												<gmd:CI_DateTypeCode codeList="http://standards.iso.org/iso/19139/resources/gmxCodelists.xml#CI_DateTypeCode" codeListValue="publication"/>
      											</gmd:dateType>
      										</gmd:CI_Date>
      									</gmd:date>
      									<gmd:identifier>
      										<gmd:MD_Identifier>
      											<gmd:code>
      												<gmx:Anchor xmlns:gmx="http://www.isotc211.org/2005/gmx" xlink:href="https://geocat-int.dev.bgdi.ch/geonetwork/srv/eng/thesaurus.download?ref=external.theme.gemet">geonetwork.thesaurus.external.theme.gemet</gmx:Anchor>
      											</gmd:code>
      										</gmd:MD_Identifier>
      									</gmd:identifier>
      								</gmd:CI_Citation>
      							</gmd:thesaurusName>
      						</gmd:MD_Keywords>
      					</gmd:descriptiveKeywords>
      				</gn_add>
      			</csw:Value>
      		</csw:RecordProperty>
      		<csw:Constraint version="1.1.0">
      			<ogc:Filter>
      				<ogc:PropertyIsEqualTo>
      					<ogc:PropertyName>Identifier</ogc:PropertyName>
      					<ogc:Literal>@Value(uuid)</ogc:Literal>
      				</ogc:PropertyIsEqualTo>
      			</ogc:Filter>
      		</csw:Constraint>
      	</csw:Update>
      </csw:Transaction>
    VAL_ATTR = post_body_add
    -> Decelerator
Decelerator
    DECEL_TYPE = Per Feature Delay
    DELAY = 2
    -> HTTPUploader
Note: CSW-T Interface Caller
HTTPUploader
    AUTH_METHOD = Basic
    AUTH_PASSWORD = $(AUTH_PASSWORD)
    AUTH_USERNAME = $(AUTH_USERNAME)
    ERROR_ATTR = _error2
    FOLLOW_REDIRECTS = Yes
    PROXY_AUTH_METHOD = Basic
    PROXY_PORT = 8080
    PROXY_URL = http://proxy-bvcol.admin.ch
    RESPONSE_HEADER_LIST_ATTR = _headers2
    STATUS_CODE_ATTR = _http_status_code2
    TARGET_ATTR = _url_contents2
    TARGET_ATTR_ENCODING = utf-8
    TARGET_URL = https://geocat-int.dev.bgdi.ch/geonetwork/srv/eng/csw-publication
    UPLOAD_BODY = @Value(post_body_add)
    UPLOAD_CONTENT_TYPE = application/xml
    UPLOAD_METHOD = POST
    USE_COOKIES = Yes
    VERIFY_SSL_CERTIFICATES = Yes
    -> http_status
    <REJECTED> -> HTTPUploader__Rejected_
http_status: TestFilter
    DEFAULT_VALUE = <UNFILTERED>
    TEST_LIST = BOOL_OP,OR,COMPOSITE_TEST,<Unused>,TEST_CLAUSE,"TEST @Value(_http_status_code) = 200",200
    200 -> TestFilter_200
    <UNFILTERED> -> TestFilter__Unfiltered_
TestFilter_200: Inspector
TestFilter__Unfiltered_: Inspector
HTTPUploader__Rejected_: Inspector

Bookmark: Delete Keyword
Note: "Schaf" wird gelöscht
create_body_delete_2: StringConcatenator
    PARM_LINE:
      <?xml version="1.0" encoding="UTF-8"?>
      <csw:Transaction service="CSW" version="2.0.2" xmlns:csw="http://www.opengis.net/cat/csw/2.0.2" xmlns:ogc="http://www.opengis.net/ogc" xmlns:apiso="http://www.opengis.net/cat/csw/apiso/1.0" xmlns:srv="http://www.isotc211.org/2005/srv" xmlns:gco="http://www.isotc211.org/2005/gco" xmlns:che="http://www.geocat.ch/2008/che" xmlns:xsi="http://www.w3.org/2001/XMLSchema-instance" xmlns:gml="http://www.opengis.net/gml" xmlns:gmd="http://www.isotc211.org/2005/gmd">
      	<csw:Update>
      		<csw:RecordProperty>
                  <csw:Name>che:CHE_MD_Metadata/gmd:identificationInfo/che:CHE_MD_DataIdentification/gmd:descriptiveKeywords/gmd:MD_Keywords/gmd:keyword/gco:CharacterString[contains(text(), 'Gemeindegrenze')]/..</csw:Name>
      			<csw:Value>
      				<gn_delete>
      				</gn_delete>
      			</csw:Value>
      		</csw:RecordProperty>
      		<csw:Constraint version="1.1.0">
      			<ogc:Filter>
      				<ogc:PropertyIsEqualTo>
      					<ogc:PropertyName>Identifier</ogc:PropertyName>
      					<ogc:Literal>@Value(uuid)</ogc:Literal>
      				</ogc:PropertyIsEqualTo>
      			</ogc:Filter>
      		</csw:Constraint>
      	</csw:Update>
      </csw:Transaction>
    VAL_ATTR = post_body_delete
    -> Decelerator_4
Decelerator_4
    DECEL_TYPE = Per Feature Delay
    DELAY = 2
    -> HTTPUploader_4
Note: CSW-T Interface Caller
HTTPUploader_4
    AUTH_METHOD = Basic
    AUTH_PASSWORD = $(AUTH_PASSWORD)
    AUTH_USERNAME = $(AUTH_USERNAME)
    ERROR_ATTR = _error
    FOLLOW_REDIRECTS = Yes
    PROXY_AUTH_METHOD = Basic
    PROXY_PORT = 8080
    PROXY_URL = http://proxy-bvcol.admin.ch
    RESPONSE_HEADER_LIST_ATTR = _headers
    STATUS_CODE_ATTR = _http_status_code
    TARGET_ATTR = _url_contents
    TARGET_ATTR_ENCODING = utf-8
    TARGET_URL = https://geocat-int.dev.bgdi.ch/geonetwork/srv/eng/csw-publication
    UPLOAD_BODY = @Value(post_body_delete)
    UPLOAD_CONTENT_TYPE = application/xml
    UPLOAD_METHOD = POST
    USE_COOKIES = Yes
    VERIFY_SSL_CERTIFICATES = Yes
    -> http_status_4
    <REJECTED> -> HTTPUploader__Rejected__4
http_status_4: TestFilter
    DEFAULT_VALUE = <UNFILTERED>
    TEST_LIST = BOOL_OP,OR,COMPOSITE_TEST,<Unused>,TEST_CLAUSE,"TEST @Value(_http_status_code) = 200",200
    200 -> TestFilter_4
    200 -> AttributeFilter_4
    <UNFILTERED> -> TestFilter__Unfiltered__4
TestFilter_4: Inspector
TestFilter__Unfiltered__4: Inspector
HTTPUploader__Rejected__4: Inspector

Bookmark: Add Keyword
Note: GEOCAT: BGDI wird hinzugefügt
StringConcatenator_5
    PARM_LINE:
      fme_basicstring:2314%12%115:<?xml version="1.0" encoding="UTF-8"?>
      <csw:Transaction service="CSW" version="2.0.2" xmlns:csw="http://www.opengis.net/cat/csw/2.0.2" xmlns:ogc="http://www.opengis.net/ogc" xmlns:apiso="http://www.opengis.net/cat/csw/apiso/1.0" xmlns:srv="http://www.isotc211.org/2005/srv" xmlns:gco="http://www.isotc211.org/2005/gco" xmlns:che="http://www.geocat.ch/2008/che" xmlns:xsi="http://www.w3.org/2001/XMLSchema-instance" xmlns:gml="http://www.opengis.net/gml" xmlns:gmd="http://www.isotc211.org/2005/gmd">
      	<csw:Update>
      		<csw:RecordProperty>
      			<csw:Name>che:CHE_MD_Metadata/gmd:identificationInfo/che:CHE_MD_DataIdentification</csw:Name>
      			<csw:Value>
      				<gn_add>
      					<gmd:descriptiveKeywords xmlns:xlink="http://www.w3.org/1999/xlink">
      						<gmd:MD_Keywords>
      							<gmd:keyword>
      								<gco:CharacterString>BGDI Bundesgeodaten-Infrastruktur</gco:CharacterString>
      							</gmd:keyword>
      							<gmd:type>
      								<gmd:MD_KeywordTypeCode codeList="http://www.isotc211.org/2005/resources/codeList.xml#MD_KeywordTypeCode" codeListValue="theme"/>
      							</gmd:type>
      							<gmd:thesaurusName>
      								<gmd:CI_Citation>
      									<gmd:title>
      										<gco:CharacterString>geocat.ch</gco:CharacterString>
      									</gmd:title>
      									<gmd:date>
      										<gmd:CI_Date>
      											<gmd:date>
      												<gco:Date>2021-06-18</gco:Date>
      											</gmd:date>
      											<gmd:dateType>
      												<gmd:CI_DateTypeCode codeList="http://standards.iso.org/iso/19139/resources/gmxCodelists.xml#CI_DateTypeCode" codeListValue="publication"/>
      											</gmd:dateType>
      										</gmd:CI_Date>
      									</gmd:date>
      									<gmd:identifier>
      										<gmd:MD_Identifier>
      											<gmd:code>
      												<gmx:Anchor xmlns:gmx="http://www.isotc211.org/2005/gmx" xlink:href="https://geocat-int.dev.bgdi.ch/geonetwork/srv/eng/thesaurus.download?ref=local.theme.geocat.ch">geonetwork.thesaurus.local.theme.geocat.ch</gmx:Anchor>
      											</gmd:code>
      										</gmd:MD_Identifier>
      									</gmd:identifier>
      								</gmd:CI_Citation>
      							</gmd:thesaurusName>
      						</gmd:MD_Keywords>
      					</gmd:descriptiveKeywords>
      				</gn_add>
      			</csw:Value>
      		</csw:RecordProperty>
      		<csw:Constraint version="1.1.0">
      			<ogc:Filter>
      				<ogc:PropertyIsEqualTo>
      					<ogc:PropertyName>Identifier</ogc:PropertyName>
      					<ogc:Literal>@Value(uuid)</ogc:Literal>
      				</ogc:PropertyIsEqualTo>
      			</ogc:Filter>
      		</csw:Constraint>
      	</csw:Update>
      </csw:Transaction>
    VAL_ATTR = post_body_add
    -> Decelerator_3
Note: GEMET: Bach wird hinzugefügt
StringConcatenator_7
    PARM_LINE:
      <?xml version="1.0" encoding="UTF-8"?>
      <csw:Transaction service="CSW" version="2.0.2" xmlns:csw="http://www.opengis.net/cat/csw/2.0.2" xmlns:ogc="http://www.opengis.net/ogc" xmlns:apiso="http://www.opengis.net/cat/csw/apiso/1.0" xmlns:srv="http://www.isotc211.org/2005/srv" xmlns:gco="http://www.isotc211.org/2005/gco" xmlns:che="http://www.geocat.ch/2008/che" xmlns:xsi="http://www.w3.org/2001/XMLSchema-instance" xmlns:gml="http://www.opengis.net/gml" xmlns:gmd="http://www.isotc211.org/2005/gmd">
      	<csw:Update>
      		<csw:RecordProperty>
      			<csw:Name>che:CHE_MD_Metadata/gmd:identificationInfo/che:CHE_MD_DataIdentification</csw:Name>
      			<csw:Value>
      				<gn_add>
      					<gmd:descriptiveKeywords xmlns:xlink="http://www.w3.org/1999/xlink">
      						<gmd:MD_Keywords>
      							<gmd:keyword xmlns:xsi="http://www.w3.org/2001/XMLSchema-instance" xsi:type="gmd:PT_FreeText_PropertyType">
      								<gco:CharacterString>Verwaltungsgrenze</gco:CharacterString>
      							</gmd:keyword>
      							<gmd:type>
      								<gmd:MD_KeywordTypeCode codeList="http://www.isotc211.org/2005/resources/codeList.xml#MD_KeywordTypeCode" codeListValue="theme"/>
      							</gmd:type>
      							<gmd:thesaurusName>
      								<gmd:CI_Citation>
      									<gmd:title>
      										<gco:CharacterString>GEMET</gco:CharacterString>
      									</gmd:title>
      									<gmd:date>
      										<gmd:CI_Date>
      											<gmd:date>
      												<gco:Date>2018-08-16</gco:Date>
      											</gmd:date>
      											<gmd:dateType>
      												<gmd:CI_DateTypeCode codeList="http://standards.iso.org/iso/19139/resources/gmxCodelists.xml#CI_DateTypeCode" codeListValue="publication"/>
      											</gmd:dateType>
      										</gmd:CI_Date>
      									</gmd:date>
      									<gmd:identifier>
      										<gmd:MD_Identifier>
      											<gmd:code>
      												<gmx:Anchor xmlns:gmx="http://www.isotc211.org/2005/gmx" xlink:href="https://geocat-int.dev.bgdi.ch/geonetwork/srv/eng/thesaurus.download?ref=external.theme.gemet">geonetwork.thesaurus.external.theme.gemet</gmx:Anchor>
      											</gmd:code>
      										</gmd:MD_Identifier>
      									</gmd:identifier>
      								</gmd:CI_Citation>
      							</gmd:thesaurusName>
      						</gmd:MD_Keywords>
      					</gmd:descriptiveKeywords>
      				</gn_add>
      			</csw:Value>
      		</csw:RecordProperty>
      		<csw:Constraint version="1.1.0">
      			<ogc:Filter>
      				<ogc:PropertyIsEqualTo>
      					<ogc:PropertyName>Identifier</ogc:PropertyName>
      					<ogc:Literal>@Value(uuid)</ogc:Literal>
      				</ogc:PropertyIsEqualTo>
      			</ogc:Filter>
      		</csw:Constraint>
      	</csw:Update>
      </csw:Transaction>
    VAL_ATTR = post_body_add
    -> Decelerator_3
Decelerator_3
    DECEL_TYPE = Per Feature Delay
    DELAY = 2
    -> HTTPUploader_3
Note: CSW-T Interface Caller
HTTPUploader_3
    AUTH_METHOD = Basic
    AUTH_PASSWORD = $(AUTH_PASSWORD)
    AUTH_USERNAME = $(AUTH_USERNAME)
    ERROR_ATTR = _error2
    FOLLOW_REDIRECTS = Yes
    PROXY_AUTH_METHOD = Basic
    PROXY_PORT = 8080
    PROXY_URL = http://proxy-bvcol.admin.ch
    RESPONSE_HEADER_LIST_ATTR = _headers2
    STATUS_CODE_ATTR = _http_status_code2
    TARGET_ATTR = _url_contents2
    TARGET_ATTR_ENCODING = utf-8
    TARGET_URL = https://geocat-int.dev.bgdi.ch/geonetwork/srv/eng/csw-publication
    UPLOAD_BODY = @Value(post_body_add)
    UPLOAD_CONTENT_TYPE = application/xml
    UPLOAD_METHOD = POST
    USE_COOKIES = Yes
    VERIFY_SSL_CERTIFICATES = Yes
    -> http_status_3
    <REJECTED> -> HTTPUploader__Rejected__3
http_status_3: TestFilter
    DEFAULT_VALUE = <UNFILTERED>
    TEST_LIST = BOOL_OP,OR,COMPOSITE_TEST,<Unused>,TEST_CLAUSE,"TEST @Value(_http_status_code) = 200",200
    200 -> TestFilter_3
    <UNFILTERED> -> TestFilter__Unfiltered__3
TestFilter_3: Inspector
TestFilter__Unfiltered__3: Inspector
HTTPUploader__Rejected__3: Inspector

FME custom transformer Starter
This transformer is intended to start a workspace branch without the use of the creator transformer. This will end up without additional attributes (_creation_instance) at the end of the workspace.

Creator
    GEOMTYPE = Geometry Object
    NUM = 1
    CREATED -> Output (output)
Output (output)
