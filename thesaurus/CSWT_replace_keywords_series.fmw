FME workspace CSWT_replace_keywords_series.fmw

Parameters:
- AUTH_PASSWORD =
- AUTH_USERNAME =
- SourceDataset_CSV2_3 =

Readers:
- CSV2_1: CSV2 from $(SourceDataset_CSV2_3)

new_keyword_present: AttributeFilter
    ATTR_NAME = new_kw_present
    ATTR_VALUES = yes,no,<Empty>,<Missing>,<Null>,<Unfiltered>
    no -> multiple_languages
multiple_languages: AttributeFilter
    ATTR_NAME = multiple_languages
    ATTR_VALUES = multiple,ger,fre,<Empty>,<Missing>,<Null>,<Unfiltered>
    multiple -> geocat_or_gemet
    ger -> geocat_or_gemet_short_de
    fre -> geocat_or_gemet_short_fr
geocat_or_gemet: AttributeFilter
    ATTR_NAME = type
    ATTR_VALUES = geocat,gemet,<Empty>,<Missing>,<Null>,<Unfiltered>
    geocat -> post_body_geocat_long
    gemet -> post_body_gemet_long
geocat_or_gemet_short_de: AttributeFilter
    ATTR_NAME = type
    ATTR_VALUES = geocat,gemet,<Empty>,<Missing>,<Null>,<Unfiltered>
    geocat -> post_body_geocat_short_de
    gemet -> post_body_gemet_short_de
geocat_or_gemet_short_fr: AttributeFilter
    ATTR_NAME = type
    ATTR_VALUES = geocat,gemet,<Empty>,<Missing>,<Null>,<Unfiltered>
    geocat -> post_body_geocat_short_fr
    gemet -> post_body_gemet_short_fr

Bookmark: Mit einer Liste von UUIDs
CSV (reader CSV2_1)
    attributes: uuid string, new_kw_present string, multiple_languages string, type string, new_kw_de string, new_kw_fr string, new_kw_en string, new_kw_it string
    -> new_keyword_present

Bookmark: Add Keyword
post_body_geocat_long: StringConcatenator
    PARM_LINE:
      <?xml version="1.0" encoding="UTF-8"?>
      <csw:Transaction service="CSW" version="2.0.2" xmlns:csw="http://www.opengis.net/cat/csw/2.0.2" xmlns:ogc="http://www.opengis.net/ogc" xmlns:apiso="http://www.opengis.net/cat/csw/apiso/1.0" xmlns:srv="http://www.isotc211.org/2005/srv" xmlns:gco="http://www.isotc211.org/2005/gco" xmlns:che="http://www.geocat.ch/2008/che" xmlns:xsi="http://www.w3.org/2001/XMLSchema-instance" xmlns:gml="http://www.opengis.net/gml" xmlns:gmd="http://www.isotc211.org/2005/gmd">
      	<csw:Update>
      		<csw:RecordProperty>
      			<csw:Name>che:CHE_MD_Metadata/gmd:identificationInfo/che:CHE_MD_DataIdentification</csw:Name>
      			<csw:Value>
      				<gn_add>
      					<gmd:descriptiveKeywords xmlns:xlink="http://www.w3.org/1999/xlink">
      						<gmd:MD_Keywords>
      							<gmd:keyword xmlns:xsi="http://www.w3.org/2001/XMLSchema-instance" xsi:type="gmd:PT_FreeText_PropertyType">
      								<gco:CharacterString>@Value(new_kw_de)</gco:CharacterString>
                                      <gmd:PT_FreeText>
      									<gmd:textGroup>
      										<gmd:LocalisedCharacterString locale="#DE">@Value(new_kw_de)</gmd:LocalisedCharacterString>
      									</gmd:textGroup>
      									<gmd:textGroup>
      										<gmd:LocalisedCharacterString locale="#FR">@Value(new_kw_fr)</gmd:LocalisedCharacterString>
      									</gmd:textGroup>
      									<gmd:textGroup>
      										<gmd:LocalisedCharacterString locale="#IT">@Value(new_kw_it)</gmd:LocalisedCharacterString>
      									</gmd:textGroup>
      									<gmd:textGroup>
      										<gmd:LocalisedCharacterString locale="#EN">@Value(new_kw_en)</gmd:LocalisedCharacterString>
      									</gmd:textGroup>
      								</gmd:PT_FreeText>
      							</gmd:keyword>
      							<gmd:type>
      								<gmd:MD_KeywordTypeCode codeList="http://www.isotc211.org/2005/resources/codeList.xml#MD_KeywordTypeCode" codeListValue="theme"/>
      							</gmd:type>
      							<gmd:thesaurusName>
      								<gmd:CI_Citation>
      									<gmd:title>
      										<gco:CharacterString>geocat.ch</gco:CharacterString>
      									</gmd:title>
      									<gmd:date>
      										<gmd:CI_Date>
      											<gmd:date>
      												<gco:Date>2021-06-18</gco:Date>
      											</gmd:date>
      											<gmd:dateType>
      												<gmd:CI_DateTypeCode codeList="http://standards.iso.org/iso/19139/resources/gmxCodelists.xml#CI_DateTypeCode" codeListValue="publication"/>
      											</gmd:dateType>
      										</gmd:CI_Date>
      									</gmd:date>
      									<gmd:identifier>
      										<gmd:MD_Identifier>
      											<gmd:code>
      												<gmx:Anchor xmlns:gmx="http://www.isotc211.org/2005/gmx" xlink:href="https://geocat-int.dev.bgdi.ch/geonetwork/srv/eng/thesaurus.download?ref=local.theme.geocat.ch">geonetwork.thesaurus.local.theme.geocat.ch</gmx:Anchor>
      											</gmd:code>
      										</gmd:MD_Identifier>
      									</gmd:identifier>
      								</gmd:CI_Citation>
      							</gmd:thesaurusName>
      						</gmd:MD_Keywords>
      					</gmd:descriptiveKeywords>
      				</gn_add>
      			</csw:Value>
      		</csw:RecordProperty>
      		<csw:Constraint version="1.1.0">
      			<ogc:Filter>
      				<ogc:PropertyIsEqualTo>
      					<ogc:PropertyName>Identifier</ogc:PropertyName>
      					<ogc:Literal>@Value(uuid)</ogc:Literal>
      				</ogc:PropertyIsEqualTo>
      			</ogc:Filter>
      		</csw:Constraint>
      	</csw:Update>
      </csw:Transaction>
    VAL_ATTR = post_body_add
    -> Decelerator
post_body_gemet_long: StringConcatenator
    PARM_LINE:
      fme_basicstring:904%17%127%17%136%17%136%17%136%17%1527%12%115:<?xml version="1.0" encoding="UTF-8"?>
      <csw:Transaction service="CSW" version="2.0.2" xmlns:csw="http://www.opengis.net/cat/csw/2.0.2" xmlns:ogc="http://www.opengis.net/ogc" xmlns:apiso="http://www.opengis.net/cat/csw/apiso/1.0" xmlns:srv="http://www.isotc211.org/2005/srv" xmlns:gco="http://www.isotc211.org/2005/gco" xmlns:che="http://www.geocat.ch/2008/che" xmlns:xsi="http://www.w3.org/2001/XMLSchema-instance" xmlns:gml="http://www.opengis.net/gml" xmlns:gmd="http://www.isotc211.org/2005/gmd">
      	<csw:Update>
      		<csw:RecordProperty>
      			<csw:Name>che:CHE_MD_Metadata/gmd:identificationInfo/che:CHE_MD_DataIdentification</csw:Name>
      			<csw:Value>
      				<gn_add>
      					<gmd:descriptiveKeywords xmlns:xlink="http://www.w3.org/1999/xlink">
      						<gmd:MD_Keywords>
      							<gmd:keyword xmlns:xsi="http://www.w3.org/2001/XMLSchema-instance" xsi:type="gmd:PT_FreeText_PropertyType">
      								<gco:CharacterString>@Value(new_kw_de)</gco:CharacterString>
      								<gmd:PT_FreeText>
      									<gmd:textGroup>
      										<gmd:LocalisedCharacterString locale="#DE">@Value(new_kw_de)</gmd:LocalisedCharacterString>
      									</gmd:textGroup>
      									<gmd:textGroup>
      										<gmd:LocalisedCharacterString locale="#FR">@Value(new_kw_fr)</gmd:LocalisedCharacterString>
      									</gmd:textGroup>
      									<gmd:textGroup>
      										<gmd:LocalisedCharacterString locale="#IT">@Value(new_kw_it)</gmd:LocalisedCharacterString>
      									</gmd:textGroup>
      									<gmd:textGroup>
      										<gmd:LocalisedCharacterString locale="#EN">@Value(new_kw_en)</gmd:LocalisedCharacterString>
      									</gmd:textGroup>
      								</gmd:PT_FreeText>
      							</gmd:keyword>
      							<gmd:type>
      								<gmd:MD_KeywordTypeCode codeList="http://www.isotc211.org/2005/resources/codeList.xml#MD_KeywordTypeCode" codeListValue="theme"/>
      							</gmd:type>
      							<gmd:thesaurusName>
      								<gmd:CI_Citation>
      									<gmd:title>
      										<gco:CharacterString>GEMET</gco:CharacterString>
      									</gmd:title>
      									<gmd:date>
      										<gmd:CI_Date>
      											<gmd:date>
      												<gco:Date>2018-08-16</gco:Date>
      											</gmd:date>
      											<gmd:dateType>
      												<gmd:CI_DateTypeCode codeList="http://standards.iso.org/iso/19139/resources/gmxCodelists.xml#CI_DateTypeCode" codeListValue="publication"/>
      											</gmd:dateType>
      										</gmd:CI_Date>
      									</gmd:date>
      									<gmd:identifier>
      										<gmd:MD_Identifier>
      											<gmd:code>
      												<gmx:Anchor xmlns:gmx="http://www.isotc211.org/2005/gmx" xlink:href="https://geocat-int.dev.bgdi.ch/geonetwork/srv/eng/thesaurus.download?ref=external.theme.gemet">geonetwork.thesaurus.external.theme.gemet</gmx:Anchor>
      											</gmd:code>
      										</gmd:MD_Identifier>
      									</gmd:identifier>
      								</gmd:CI_Citation>
      							</gmd:thesaurusName>
      						</gmd:MD_Keywords>
      					</gmd:descriptiveKeywords>
      				</gn_add>
      			</csw:Value>
      		</csw:RecordProperty>
      		<csw:Constraint version="1.1.0">
      			<ogc:Filter>
      				<ogc:PropertyIsEqualTo>
      					<ogc:PropertyName>Identifier</ogc:PropertyName>
      					<ogc:Literal>@Value(uuid)</ogc:Literal>
      				</ogc:PropertyIsEqualTo>
      			</ogc:Filter>
      		</csw:Constraint>
      	</csw:Update>
      </csw:Transaction>
    VAL_ATTR = post_body_add
    -> Decelerator
post_body_geocat_short_de: StringConcatenator
    PARM_LINE:
      fme_basicstring:810%17%1471%12%115:<?xml version="1.0" encoding="UTF-8"?>
      <csw:Transaction service="CSW" version="2.0.2" xmlns:csw="http://www.opengis.net/cat/csw/2.0.2" xmlns:ogc="http://www.opengis.net/ogc" xmlns:apiso="http://www.opengis.net/cat/csw/apiso/1.0" xmlns:srv="http://www.isotc211.org/2005/srv" xmlns:gco="http://www.isotc211.org/2005/gco" xmlns:che="http://www.geocat.ch/2008/che" xmlns:xsi="http://www.w3.org/2001/XMLSchema-instance" xmlns:gml="http://www.opengis.net/gml" xmlns:gmd="http://www.isotc211.org/2005/gmd">
      	<csw:Update>
      		<csw:RecordProperty>
      			<csw:Name>che:CHE_MD_Metadata/gmd:identificationInfo/che:CHE_MD_DataIdentification</csw:Name>
      			<csw:Value>
      				<gn_add>
      					<gmd:descriptiveKeywords xmlns:xlink="http://www.w3.org/1999/xlink">
      						<gmd:MD_Keywords>
      							<gmd:keyword>
      								<gco:CharacterString>@Value(new_kw_de)</gco:CharacterString>
      							</gmd:keyword>
      							<gmd:type>
      								<gmd:MD_KeywordTypeCode codeList="http://www.isotc211.org/2005/resources/codeList.xml#MD_KeywordTypeCode" codeListValue="theme"/>
      							</gmd:type>
      							<gmd:thesaurusName>
      								<gmd:CI_Citation>
      									<gmd:title>
      										<gco:CharacterString>geocat.ch</gco:CharacterString>
      									</gmd:title>
      									<gmd:date>
      										<gmd:CI_Date>
      											<gmd:date>
      												<gco:Date>2021-06-18</gco:Date>
      											</gmd:date>
      											<gmd:dateType>
      												<gmd:CI_DateTypeCode codeList="http://standards.iso.org/iso/19139/resources/gmxCodelists.xml#CI_DateTypeCode" codeListValue="publication"/>
      											</gmd:dateType>
      										</gmd:CI_Date>
      									</gmd:date>
      									<gmd:identifier>
      										<gmd:MD_Identifier>
      											<gmd:code>
      												<gmx:Anchor xmlns:gmx="http://www.isotc211.org/2005/gmx" xlink:href="https://geocat-int.dev.bgdi.ch/geonetwork/srv/eng/thesaurus.download?ref=local.theme.geocat.ch">geonetwork.thesaurus.local.theme.geocat.ch</gmx:Anchor>
      											</gmd:code>
      										</gmd:MD_Identifier>
      									</gmd:identifier>
      								</gmd:CI_Citation>
      							</gmd:thesaurusName>
      						</gmd:MD_Keywords>
      					</gmd:descriptiveKeywords>
      				</gn_add>
      			</csw:Value>
      		</csw:RecordProperty>
      		<csw:Constraint version="1.1.0">
      			<ogc:Filter>
      				<ogc:PropertyIsEqualTo>
      					<ogc:PropertyName>Identifier</ogc:PropertyName>
      					<ogc:Literal>@Value(uuid)</ogc:Literal>
      				</ogc:PropertyIsEqualTo>
      			</ogc:Filter>
      		</csw:Constraint>
      	</csw:Update>
      </csw:Transaction>
    VAL_ATTR = post_body_add
    -> Decelerator
post_body_gemet_short_de: StringConcatenator
    PARM_LINE:
      fme_basicstring:904%17%1465%12%115:<?xml version="1.0" encoding="UTF-8"?>
      <csw:Transaction service="CSW" version="2.0.2" xmlns:csw="http://www.opengis.net/cat/csw/2.0.2" xmlns:ogc="http://www.opengis.net/ogc" xmlns:apiso="http://www.opengis.net/cat/csw/apiso/1.0" xmlns:srv="http://www.isotc211.org/2005/srv" xmlns:gco="http://www.isotc211.org/2005/gco" xmlns:che="http://www.geocat.ch/2008/che" xmlns:xsi="http://www.w3.org/2001/XMLSchema-instance" xmlns:gml="http://www.opengis.net/gml" xmlns:gmd="http://www.isotc211.org/2005/gmd">
      	<csw:Update>
      		<csw:RecordProperty>
      			<csw:Name>che:CHE_MD_Metadata/gmd:identificationInfo/che:CHE_MD_DataIdentification</csw:Name>
      			<csw:Value>
      				<gn_add>
      					<gmd:descriptiveKeywords xmlns:xlink="http://www.w3.org/1999/xlink">
      						<gmd:MD_Keywords>
      							<gmd:keyword xmlns:xsi="http://www.w3.org/2001/XMLSchema-instance" xsi:type="gmd:PT_FreeText_PropertyType">
      								<gco:CharacterString>@Value(new_kw_de)</gco:CharacterString>
      							</gmd:keyword>
      							<gmd:type>
      								<gmd:MD_KeywordTypeCode codeList="http://www.isotc211.org/2005/resources/codeList.xml#MD_KeywordTypeCode" codeListValue="theme"/>
      							</gmd:type>
      							<gmd:thesaurusName>
      								<gmd:CI_Citation>
      									<gmd:title>
      										<gco:CharacterString>GEMET</gco:CharacterString>
      									</gmd:title>
      									<gmd:date>
      										<gmd:CI_Date>
      											<gmd:date>
      												<gco:Date>2018-08-16</gco:Date>
      											</gmd:date>
      											<gmd:dateType>
      												<gmd:CI_DateTypeCode codeList="http://standards.iso.org/iso/19139/resources/gmxCodelists.xml#CI_DateTypeCode" codeListValue="publication"/>
      											</gmd:dateType>
      										</gmd:CI_Date>
      									</gmd:date>
      									<gmd:identifier>
      										<gmd:MD_Identifier>
      											<gmd:code>
      												<gmx:Anchor xmlns:gmx="http://www.isotc211.org/2005/gmx" xlink:href="https://geocat-int.dev.bgdi.ch/geonetwork/srv/eng/thesaurus.download?ref=external.theme.gemet">geonetwork.thesaurus.external.theme.gemet</gmx:Anchor>
      											</gmd:code>
      										</gmd:MD_Identifier>
      									</gmd:identifier>
      								</gmd:CI_Citation>
      							</gmd:thesaurusName>
      						</gmd:MD_Keywords>
      					</gmd:descriptiveKeywords>
      				</gn_add>
      			</csw:Value>
      		</csw:RecordProperty>
      		<csw:Constraint version="1.1.0">
      			<ogc:Filter>
      				<ogc:PropertyIsEqualTo>
      					<ogc:PropertyName>Identifier</ogc:PropertyName>
      					<ogc:Literal>@Value(uuid)</ogc:Literal>
      				</ogc:PropertyIsEqualTo>
      			</ogc:Filter>
      		</csw:Constraint>
      	</csw:Update>
      </csw:Transaction>
    VAL_ATTR = post_body_add
    -> Decelerator
post_body_geocat_short_fr: StringConcatenator
    PARM_LINE:
      fme_basicstring:810%17%1471%12%115:<?xml version="1.0" encoding="UTF-8"?>
      <csw:Transaction service="CSW" version="2.0.2" xmlns:csw="http://www.opengis.net/cat/csw/2.0.2" xmlns:ogc="http://www.opengis.net/ogc" xmlns:apiso="http://www.opengis.net/cat/csw/apiso/1.0" xmlns:srv="http://www.isotc211.org/2005/srv" xmlns:gco="http://www.isotc211.org/2005/gco" xmlns:che="http://www.geocat.ch/2008/che" xmlns:xsi="http://www.w3.org/2001/XMLSchema-instance" xmlns:gml="http://www.opengis.net/gml" xmlns:gmd="http://www.isotc211.org/2005/gmd">
      	<csw:Update>
      		<csw:RecordProperty>
      			<csw:Name>che:CHE_MD_Metadata/gmd:identificationInfo/che:CHE_MD_DataIdentification</csw:Name>
      			<csw:Value>
      				<gn_add>
      					<gmd:descriptiveKeywords xmlns:xlink="http://www.w3.org/1999/xlink">
      						<gmd:MD_Keywords>
      							<gmd:keyword>
      								<gco:CharacterString>@Value(new_kw_fr)</gco:CharacterString>
      							</gmd:keyword>
      							<gmd:type>
      								<gmd:MD_KeywordTypeCode codeList="http://www.isotc211.org/2005/resources/codeList.xml#MD_KeywordTypeCode" codeListValue="theme"/>
      							</gmd:type>
      							<gmd:thesaurusName>
      								<gmd:CI_Citation>
      									<gmd:title>
      										<gco:CharacterString>geocat.ch</gco:CharacterString>
      									</gmd:title>
      									<gmd:date>
      										<gmd:CI_Date>
      											<gmd:date>
      												<gco:Date>2021-06-18</gco:Date>
      											</gmd:date>
      											<gmd:dateType>
      												<gmd:CI_DateTypeCode codeList="http://standards.iso.org/iso/19139/resources/gmxCodelists.xml#CI_DateTypeCode" codeListValue="publication"/>
      											</gmd:dateType>
      										</gmd:CI_Date>
      									</gmd:date>
      									<gmd:identifier>
      										<gmd:MD_Identifier>
      											<gmd:code>
      												<gmx:Anchor xmlns:gmx="http://www.isotc211.org/2005/gmx" xlink:href="https://geocat-int.dev.bgdi.ch/geonetwork/srv/eng/thesaurus.download?ref=local.theme.geocat.ch">geonetwork.thesaurus.local.theme.geocat.ch</gmx:Anchor>
      											</gmd:code>
      										</gmd:MD_Identifier>
      									</gmd:identifier>
      								</gmd:CI_Citation>
      							</gmd:thesaurusName>
      						</gmd:MD_Keywords>
      					</gmd:descriptiveKeywords>
      				</gn_add>
      			</csw:Value>
      		</csw:RecordProperty>
      		<csw:Constraint version="1.1.0">
      			<ogc:Filter>
      				<ogc:PropertyIsEqualTo>
      					<ogc:PropertyName>Identifier</ogc:PropertyName>
      					<ogc:Literal>@Value(uuid)</ogc:Literal>
      				</ogc:PropertyIsEqualTo>
      			</ogc:Filter>
      		</csw:Constraint>
      	</csw:Update>
      </csw:Transaction>
    VAL_ATTR = post_body_add
    -> Decelerator
post_body_gemet_short_fr: StringConcatenator
    PARM_LINE:
      fme_basicstring:904%17%1465%12%115:<?xml version="1.0" encoding="UTF-8"?>
      <csw:Transaction service="CSW" version="2.0.2" xmlns:csw="http://www.opengis.net/cat/csw/2.0.2" xmlns:ogc="http://www.opengis.net/ogc" xmlns:apiso="http://www.opengis.net/cat/csw/apiso/1.0" xmlns:srv="http://www.isotc211.org/2005/srv" xmlns:gco="http://www.isotc211.org/2005/gco" xmlns:che="http://www.geocat.ch/2008/che" xmlns:xsi="http://www.w3.org/2001/XMLSchema-instance" xmlns:gml="http://www.opengis.net/gml" xmlns:gmd="http://www.isotc211.org/2005/gmd">
      	<csw:Update>
      		<csw:RecordProperty>
      			<csw:Name>che:CHE_MD_Metadata/gmd:identificationInfo/che:CHE_MD_DataIdentification</csw:Name>
      			<csw:Value>
      				<gn_add>
      					<gmd:descriptiveKeywords xmlns:xlink="http://www.w3.org/1999/xlink">
      						<gmd:MD_Keywords>
      							<gmd:keyword xmlns:xsi="http://www.w3.org/2001/XMLSchema-instance" xsi:type="gmd:PT_FreeText_PropertyType">
      								<gco:CharacterString>@Value(new_kw_fr)</gco:CharacterString>
      							</gmd:keyword>
      							<gmd:type>
      								<gmd:MD_KeywordTypeCode codeList="http://www.isotc211.org/2005/resources/codeList.xml#MD_KeywordTypeCode" codeListValue="theme"/>
      							</gmd:type>
      							<gmd:thesaurusName>
      								<gmd:CI_Citation>
      									<gmd:title>
      										<gco:CharacterString>GEMET</gco:CharacterString>
      									</gmd:title>
      									<gmd:date>
      										<gmd:CI_Date>
      											<gmd:date>
      												<gco:Date>2018-08-16</gco:Date>
      											</gmd:date>
      											<gmd:dateType>
      												<gmd:CI_DateTypeCode codeList="http://standards.iso.org/iso/19139/resources/gmxCodelists.xml#CI_DateTypeCode" codeListValue="publication"/>
      											</gmd:dateType>
      										</gmd:CI_Date>
      									</gmd:date>
      									<gmd:identifier>
      										<gmd:MD_Identifier>
      											<gmd:code>
      												<gmx:Anchor xmlns:gmx="http://www.isotc211.org/2005/gmx" xlink:href="https://geocat-int.dev.bgdi.ch/geonetwork/srv/eng/thesaurus.download?ref=external.theme.gemet">geonetwork.thesaurus.external.theme.gemet</gmx:Anchor>
      											</gmd:code>
      										</gmd:MD_Identifier>
      									</gmd:identifier>
      								</gmd:CI_Citation>
      							</gmd:thesaurusName>
      						</gmd:MD_Keywords>
      					</gmd:descriptiveKeywords>
      				</gn_add>
      			</csw:Value>
      		</csw:RecordProperty>
      		<csw:Constraint version="1.1.0">
      			<ogc:Filter>
      				<ogc:PropertyIsEqualTo>
      					<ogc:PropertyName>Identifier</ogc:PropertyName>
      					<ogc:Literal>@Value(uuid)</ogc:Literal>
      				</ogc:PropertyIsEqualTo>
      			</ogc:Filter>
      		</csw:Constraint>
      	</csw:Update>
      </csw:Transaction>
    VAL_ATTR = post_body_add
    -> Decelerator
Decelerator
    DECEL_TYPE = Per Feature Delay
    DELAY = 2
    -> HTTPUploader
Note: CSW-T Interface Caller
HTTPUploader
    AUTH_METHOD = Basic
    AUTH_PASSWORD = $(AUTH_PASSWORD)
    AUTH_USERNAME = $(AUTH_USERNAME)
    ERROR_ATTR = _error
    FOLLOW_REDIRECTS = Yes
    PROXY_AUTH_METHOD = Basic
    PROXY_PORT = 8080
    PROXY_URL = http://proxy-bvcol.admin.ch
    RESPONSE_HEADER_LIST_ATTR = _headers
    STATUS_CODE_ATTR = _http_status_code
    TARGET_ATTR = _url_contents
    TARGET_ATTR_ENCODING = utf-8
    TARGET_URL = https://www.geocat.ch/geonetwork/srv/eng/csw-publication
    UPLOAD_BODY = @Value(post_body_add)
    UPLOAD_CONTENT_TYPE = application/xml
    UPLOAD_METHOD = POST
    USE_COOKIES = Yes
    VERIFY_SSL_CERTIFICATES = Yes
    -> http_status
    <REJECTED> -> HTTPUploader__Rejected_
http_status: TestFilter
    DEFAULT_VALUE = <UNFILTERED>
    TEST_LIST = BOOL_OP,OR,COMPOSITE_TEST,<Unused>,TEST_CLAUSE,"TEST @Value(_http_status_code) = 200",200
    200 -> TestFilter_200
    <UNFILTERED> -> TestFilter__Unfiltered_
TestFilter_200: Inspector
TestFilter__Unfiltered_: Inspector
HTTPUploader__Rejected_: Inspector
