FME workspace CSWT_delete_keyword_missing.fmw

Parameters:
- AUTH_PASSWORD =
- AUTH_USERNAME =
- SourceDataset_CSV2_3 =

Readers:
- CSV2_1: CSV2 from $(SourceDataset_CSV2_3)

StringConcatenator_2
    PARM_LINE:
      <?xml version="1.0" encoding="UTF-8"?>
      <csw:Transaction service="CSW" version="2.0.2" xmlns:csw="http://www.opengis.net/cat/csw/2.0.2" xmlns:ogc="http://www.opengis.net/ogc" xmlns:apiso="http://www.opengis.net/cat/csw/apiso/1.0" xmlns:srv="http://www.isotc211.org/2005/srv" xmlns:gco="http://www.isotc211.org/2005/gco" xmlns:che="http://www.geocat.ch/2008/che" xmlns:xsi="http://www.w3.org/2001/XMLSchema-instance" xmlns:gml="http://www.opengis.net/gml" xmlns:gmd="http://www.isotc211.org/2005/gmd">
      	<csw:Update>
      		<csw:RecordProperty>
      			<csw:Name>/che:CHE_MD_Metadata/gmd:identificationInfo/che:CHE_MD_DataIdentification/gmd:descriptiveKeywords/gmd:MD_Keywords/gmd:keyword[@gco:nilReason = 'missing']/../..</csw:Name>
      			<csw:Value>
      				<gn_delete>
      				</gn_delete>
      			</csw:Value>
      		</csw:RecordProperty>
      		<csw:Constraint version="1.1.0">
      			<ogc:Filter>
      				<ogc:PropertyIsEqualTo>
      					<ogc:PropertyName>Identifier</ogc:PropertyName>
      					<ogc:Literal>@Value(uuid)</ogc:Literal>
      				</ogc:PropertyIsEqualTo>
      			</ogc:Filter>
      		</csw:Constraint>
      	</csw:Update>
      </csw:Transaction>
    VAL_ATTR = post_body
    -> Decelerator

Bookmark: Test mit nur einer UUID
Starter [off]
    -> AttributeCreator [off]
AttributeCreator [off]
    ATTR_TABLE = SET_TO uuid = 0bc5786a-6bb3-4bd1-90d2-f49bed32a697
    -> StringConcatenator_2

Bookmark: Mit einer Liste von UUIDs
CSV (reader CSV2_1)
    attributes: uuid string, title string, org string
    -> StringConcatenator_2

Bookmark: create post body and call csw-t interface
Decelerator
    DECEL_TYPE = Per Feature Delay
    DELAY = 1
    -> HTTPUploader
Note: CSW-T Interface Caller
HTTPUploader
    AUTH_METHOD = Basic
    AUTH_PASSWORD = $(AUTH_PASSWORD)
    AUTH_USERNAME = $(AUTH_USERNAME)
    ERROR_ATTR = _error
    FOLLOW_REDIRECTS = Yes
    PROXY_AUTH_METHOD = Basic
    PROXY_PORT = 8080
    PROXY_URL = http://proxy-bvcol.admin.ch
    RESPONSE_HEADER_LIST_ATTR = _headers
    STATUS_CODE_ATTR = _http_status_code
    TARGET_ATTR = _url_contents
    TARGET_ATTR_ENCODING = utf-8
    TARGET_URL = https://www.geocat.ch/geonetwork/srv/eng/csw-publication
    UPLOAD_BODY = @Value(post_body)
    UPLOAD_CONTENT_TYPE = application/xml
    UPLOAD_METHOD = POST
    USE_COOKIES = Yes
    VERIFY_SSL_CERTIFICATES = Yes
    -> http_status
    <REJECTED> -> HTTPUploader__Rejected_
http_status: TestFilter
    DEFAULT_VALUE = <UNFILTERED>
    TEST_LIST = BOOL_OP,OR,COMPOSITE_TEST,<Unused>,TEST_CLAUSE,"TEST @Value(_http_status_code) = 200",200
    200 -> TestFilter_200
    <UNFILTERED> -> TestFilter__Unfiltered_
TestFilter_200: Inspector
TestFilter__Unfiltered_: Inspector
HTTPUploader__Rejected_: Inspector

FME custom transformer Starter
This transformer is intended to start a workspace branch without the use of the creator transformer. This will end up without additional attributes (_creation_instance) at the end of the workspace.

Creator
    GEOMTYPE = Geometry Object
    NUM = 1
    CREATED -> Output (output)
Output (output)
